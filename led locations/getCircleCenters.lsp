;;;; from http://www.cadtutor.net/forum/showthread.php?12172-help-extract-pile-coordinates&highlight=coordinates%20to%20file

(princ "\nType PTF to start")
(defun c:ptf ()
   (setq FileName (getstring "\nEnter file name for coordinate output: "))
   (setq f1 (open FileName "w"))
   (princ "\nSelect circles to write to file: ")
;;;   (setq PointSet (ssget '((0 . "CIRCLE"))))
   (setq PointSet (ssget ))
   (setq EntNum 0)
   (repeat (sslength PointSet)
       (setq ename (ssname PointSet EntNum))
       (setq PtCoord (cdr (assoc 10 (entget ename))))
       (setq xval (rtos (car PtCoord) 2 4)
             yval (rtos (cadr PtCoord) 2 4)
             zval (rtos (caddr PtCoord) 2 4)
             PtString (strcat xval "," yval "," zval)
       )
       (write-line PtString f1)
       (setq EntNum (1+ EntNum))
   )
   (close f1)
   (princ)
)
